--/*********************************************************************************/
--/* FileName:      ufsm_log.asn                                                   */
--/* Description:   H2ASN TOOLS Generate ASN.1 file                                */
--/* CopyRight:     Huawei Technologies Co., Ltd.                                  */
--/* Created By:                                                                   */
--/* HISTORY VER:   NULL                                                           */
--/* VERSION:       1.0                                                            */
--/* Create Time:   2015.8.25 14:5:7                                               */
--/* Create Option: H2ASN C:\Users\f73150\AppData\Local\Temp\Huawei\Daisy\ufsm_log_ASNfile\ufsm_log.h C:\Users\f73150\AppData\Local\Temp\Huawei\Daisy\ufsm_log_ASNfile\ufsm_log.asn*/
--/*********************************************************************************/
                                                                                   
--ROOT    : Ufsm-log-definitions.Ufsm-log-MSG                                              
--PROTOCOL: Ufsm-log                                                                     
--ENDIAN  : LITTLE                                                                   
--BOUNDARY: ALIGN                                                                    
--THREAD  : MULTI                                                                    
                                                                                     
Ufsm-log-definitions DEFINITIONS ::=                                                             
BEGIN                                                                                
                                                                                   
VOS-UINT8  ::= <V,V|LEN-8>INTEGER(0..255) 

VOS-UINT16 ::= <V,V|LEN-16>INTEGER(0..65535) 

VOS-INT16  ::= <V,V|LEN-16>INTEGER(-32768..32767) 

VOS-UINT32 ::= <V,V|LEN-32>INTEGER(0..4294967295) 

VOS-INT32  ::= <V,V|LEN-32>INTEGER(-2147483648..2147483647) 

VOS-MSG-HEADER  ::= <V>SEQUENCE 
{ 
    ulSenderCpuId    VOS-UINT32, 
    ulSenderPid      VOS-UINT32, 
    ulReceiverCpuId  VOS-UINT32, 
    ulReceiverPid    VOS-UINT32 
} 

VOS-RATMODE-ENUM    ::= <V,V|LEN-32> ENUMERATED  
{ 
    vOS-RATMODE-GSM(0), 
    vOS-RATMODE-WCDMA(1), 
    vOS-RATMODE-LTE(2), 
    vOS-RATMODE-TDS(3), 
    vOS-RATMODE-1X(4), 
    vOS-RATMODE-EVDO(5), 
    vOS-RATMODE-BUTT(6) 
} 

MODEM-ID-ENUM    ::= <V,V|LEN-16> ENUMERATED  
{ 
    mODEM-ID-BUTT(0) 
} 

MsgBlock    ::= <V> SEQUENCE  
{ 
     
    dummy    <V>SEQUENCE(SIZE(4)) OF VOS-UINT8 
} 

PHY-UINT32  ::= <V,V|LEN-32>VOS-UINT32 

PHY-UINT16  ::= <V,V|LEN-16>VOS-UINT16 

Uint32-t  ::= <V,V|LEN-32>VOS-UINT32 

UFSM-LOG-MSG-TYPE-ENUM    ::= <V,V|LEN-16> ENUMERATED  
{ 
    iD-UFSM-LogMsg(22400),    --/* -H2ASN-MsgChoice UFSM-LogMsg-STRU */ 
    iD-UFSM-LOG-MSG-TYPE-ENUM-BUTT(65535) 
} 

UFSM-LOG-MSG-TYPE-ENUM-CHOICE-STRU    ::= <V|WHEN>CHOICE 
{ 
   struUFSM-LogMsg-STRU   UFSM-LogMsg-STRU   WHEN(usChoice1.v==22400) 
} 

UFSM-MSG-ENUM    ::= <V,V|LEN-32> ENUMERATED  
{ 
    uFSM-LOG-STATE-CHANGE(578000),    --/* -H2ASN-MsgChoice StateChange */ 
    uFSM-LOG-EVENT(578001),    --/* -H2ASN-MsgChoice NewEvent */ 
    uFSM-LOG-OUT-OF-RANGE(578002),    --/* -H2ASN-MsgChoice StateError */ 
    uFSM-LOG-ENTER-ERROR-STATE(578003),    --/* -H2ASN-MsgChoice ErrorCode */ 
    uFSM-MSG-ENUM-BUTT(578004) 
} 

UFSM-MSG-ENUM-CHOICE-STRU    ::= <V|WHEN,V|UNION-1>CHOICE 
{ 
   struStateChange   StateChange   WHEN(usChoice2.v==578000), 
   struNewEvent   NewEvent   WHEN(usChoice2.v==578001), 
   struStateError   StateError   WHEN(usChoice2.v==578002), 
   struErrorCode   ErrorCode   WHEN(usChoice2.v==578003) 
} 

ErrorCode    ::= <V> SEQUENCE  
{ 
    current-state    Uint32-t , 
 
    error-code    Uint32-t  
} 

NewEvent    ::= <V> SEQUENCE  
{ 
    current-state    Uint32-t , 
 
    event    Uint32-t  
} 

StateChange    ::= <V> SEQUENCE  
{ 
    current-state    Uint32-t , 
 
    new-state    Uint32-t  
} 

StateError    ::= <V> SEQUENCE  
{ 
    current-state    Uint32-t , 
 
    new-error-state    Uint32-t  
} 

UFSM-LogMsg-STRU    ::= <V> SEQUENCE  
{ 
    --// VOS-MSG-HEADER 
 
    --// UFSM-LOG-MSG-TYPE-ENUM-UINT16 enMsgId; 
 
    uhwOpId    PHY-UINT16 , 
 
    log-reason    <V,V|LEN-32>UFSM-MSG-ENUM  EXPORT(usChoice2), 
 
    --/* -H2ASN-MsgChoice-Export UFSM-MSG-ENUM-UINT32 */ 
    --logType    u 
    struMsgChoice    UFSM-MSG-ENUM-CHOICE-STRU, 
 
    --/* -H2ASN-MsgChoice-When-Comment UFSM-MSG-ENUM-UINT32 */ 
    extra    Uint32-t  
} 

Ufsm-log-msg-data    ::= <LV,L|LEN-32> SEQUENCE  
{ 
    enMsgId    <V,V|LEN-16>UFSM-LOG-MSG-TYPE-ENUM  EXPORT(usChoice1), 
 
    --/* -H2ASN-MsgChoice-Export UFSM-LOG-MSG-TYPE-ENUM-UINT16 */ 
    --DummySignalUnion    dummySignalUnion 
    struMsgChoice    UFSM-LOG-MSG-TYPE-ENUM-CHOICE-STRU 
    --/* -H2ASN-MsgChoice-When-Comment UFSM-LOG-MSG-TYPE-ENUM-UINT16 */ 
} 

Ufsm-log-MSG    ::= <V> SEQUENCE  
{ 
    vOS-MSG-HEADER  VOS-MSG-HEADER, 
 
    stMsgData    Ufsm-log-msg-data  
} 

Ufsm-log-DUMMY-STRUCT-TO-MAKE-H2ASN1-WORK    ::= <V> SEQUENCE  
{ 
    dummy    VOS-UINT32  
} 

END
